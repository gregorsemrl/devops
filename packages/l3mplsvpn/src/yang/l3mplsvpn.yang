module l3mplsvpn {
  namespace "http://example.com/l3mplsvpn";
  prefix l3mplsvpn;

  import ietf-inet-types {
    prefix inet;
  }

  import tailf-ncs {
    prefix ncs;
  }

  import tailf-common {
    prefix tailf;
  }

  import tailf-ned-cisco-ios {
    prefix ios;
  }

  import tailf-ned-cisco-ios-xr {
    prefix iosxr;
  }

  description "Service for L3 MPLS VPN provisioning with subscriber.";

  revision 2018-06-04 {
    description
      "Initial revision.";
  }

  augment /ncs:services {
    list l3mplsvpn {
      uses ncs:service-data;
      ncs:servicepoint l3mplsvpn-servicepoint;
      key name;

      leaf name {
        tailf:info "Service Instance Name";
        type string;
      }

      leaf customer {
        tailf:info "VPN Customer";
        mandatory true;
        type leafref {
          path "/ncs:customers/ncs:customer/ncs:id";
        }
      }

      list link {
        tailf:info "PE-CE Attachment Point";
        key link-id;
        min-elements 1;
        unique "device ios/interface";
        unique "device iosxr/interface";

        leaf link-id {
          tailf:info "Link ID (1 to 65535)";
          type uint32 {
            range "1..65535" {
              error-message "Link ID is out of range. Should be between 1 and 65535.";
            }
          }
        }

        leaf device {
          tailf:info "PE Router";
          mandatory true;
          type leafref {
            path "/ncs:devices/ncs:device/ncs:name";
          }
          must "starts-with(current(),'PE')" {
            error-message "Only PE devices can be selected.";
          }
        }

        leaf routing-protocol {
          tailf:info "Routing option for the PE-CE link";
          type enumeration {
            enum bgp;
            enum rip;
          }
          default bgp;
        }

        leaf pe-ip {
          tailf:info "PE-CE Link IP Address";
            type inet:ipv4-address {
              pattern "172\.(1[6-9]|2[0-9]|3[0-1])\..*" {
                error-message "Invalid IP address. IP address should be in the 172.16.0.0/12 range.";
              }
            }
        }

        leaf ce-ip {
          tailf:info "CE Neighbor IP Address";
          when "../routing-protocol='bgp'";
            type inet:ipv4-address;
        }

        leaf rip-net {
          tailf:info "IP Network for RIP";
          when "../routing-protocol='rip'";
            type inet:ipv4-address;
        }

         /* This device specific containers are here only to show the versatility of yang and how autocompletion can be
        provided. Do not use this in production since it breaks the principle of vendor independent service model.*/
        container ios {
          when "deref(../device)/../ncs:module[1]/ncs:name='tailf-ned-cisco-ios'" {
            tailf:dependency "../device";
          }
          tailf:cli-drop-node-name;

          leaf interface{
            tailf:info "Customer Facing Interface";
            mandatory true;
            type leafref {
              path "deref(../../device)/../ncs:config/ios:interface/ios:GigabitEthernet/ios:name";
            }
            must "count(../../../../l3mplsvpn[name != current()/../../../name]/link[device = current()/../../device]/ios/interface = current()) = 0" {
              error-message "Interface is already used for another link.";
            }
          }
        }

        container iosxr {
          when "deref(../device)/../ncs:module[1]/ncs:name='tailf-ned-cisco-ios-xr'" {
            tailf:dependency "../device";
          }
          tailf:cli-drop-node-name;

          leaf interface{
            tailf:info "Customer Facing Interface";
            mandatory true;
            type leafref {
              path "deref(../../device)/../ncs:config/iosxr:interface/iosxr:GigabitEthernet/iosxr:id";
            }
            must "count(../../../../l3mplsvpn[name != current()/../../../name]/link[device = current()/../../device]/iosxr/interface = current()) = 0" {
              error-message "Interface is already used for another link.";
            }
          }
        }
      }
    }
  }
}
